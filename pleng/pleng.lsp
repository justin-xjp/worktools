;;;===================== 主程序==============================
(print "多段线累积长度标识")
(print "PLeng")

(defun C:pleng ()
;;;选择一条PLINE，或是指定标注比例，默认1/1
  ;;(setq outScale 1)
  (setq ss1 (ssget '((0 . "LWPOLYLINE"))))
  (setq ent (entget (ssname ss1 0)))
  (setq pts nil)
  (setq plpdelta nil)
  (setq plengDis nil)
  ;;;循环计算得到点坐标
  (setq i 0)
  (repeat (length ent)
    (if	(= (car (nth i ent)) 10)
      (setq pts (append pts (list (cdr (nth i ent)))))
    )
    (setq i (1+ i))
  )
  
  ;;;计算分段长度和累计长度
  (setq i 0)
  (setq plengDis (append plengDis (list 0.000)))
  (repeat (- (length pts) 1)
    (setq curntDis (list (distance (nth i pts) (nth (+ i 1) pts))))				;;;求两点间距离
    (setq plpdelta (append plpdelta curntDis))
    (setq plengDis (append plengDis  (list (+ (car curntDis) (nth i plengDis)))))
    (setq i (1+ i))
  )
  (print plpdelta)
  (print plengDis)
  (print pts)
  (princ)
;;;依次在多段线的点上输出信息。
  (setq outScale (getint "请输入比例（1、2、4）<1>:"))
  (if (not outScale)(setq outScale 1))
  (setq i 0)
  ;;默认文字和相对点位
  (setq tH (* outScale 3))
  ;; (setq noteLinelength (* outScale 7.5))
  ;; (setq lpt (list noteLinelength noteLinelength))
  ;; (setq mpt (list (* 2 noteLinelength) noteLinelength))
  ;; (setq rpt (list (* 3 noteLinelength) noteLinelength))
  (repeat (length pts)
	(setq cpt (nth i pts))
	;; (setq clpt (mapcar '+ cpt lpt))
	;; (setq crpt (mapcar '+ cpt rpt))
	;; (setq cmpt (mapcar '+ cpt mpt))
	(setq infotext (strcat "0+" (vl-princ-to-string (nth i plengDis))))
	;; (command "_.pline" cpt clpt crpt )
	;; (command)	
	(command "_text" "J" "TC" cpt tH "0" infotext)
	(command)
	(setq i (1+ i))
  )
)
