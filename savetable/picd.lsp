(defun c:picd (/ p1 p2 ttl)
  (setvar "modemacro" "picd=running")
  (command "_.undo" "m")
  (command)

  (setvar "CECOLOR" "yellow")
  (command "_.linetype" "s" "dash" "")
  
  (command)
  (print)
  (setq s1 (getpoint "点取s1"))
  (command "_.boundary" "a" "i" "n" "" "" s1 "")
  (command)
  (setq e (entlast))
  (command)
  (setq e (entget e))
  (setq p1 (cdr (assoc 10 e)))
  (setq e (cdr (member (assoc 10 e) e)))
  (while (or (= (cadr (assoc 10 e)) (car p1)) (= (caddr (assoc 10 e)) (cadr p1)))
     (setq e (cdr (member (assoc 10 e) e)))
  )
  (setq p2 (cdr (assoc 10 e)))
  ;(setq p2 (getpoint "点取P2"))
;|
  (command "_.point" (mapcar '+ p1 '(100 100)))
  (command)
  (command "_.point" (mapcar '+ p2 '(-100 -100)))
  (command)
  (command "_zoom" "w" p1 p2)
  (command)
  (if (or (setq ttl (ssget "w" (mapcar '+ p1 '(-10 10)) (mapcar '+ p2 '(10 -10)) '((0 . "text"))))
	  (setq ttl (ssget "w" (mapcar '+ p1 '(-10 10)) (mapcar '+ p2 '(10 -10)) '((0 . "mtext"))))
      )
    (progn
      (print (cdr (assoc 1 (entget (ssname ttl 0)))))
    )
   )
 )
 |;

)
